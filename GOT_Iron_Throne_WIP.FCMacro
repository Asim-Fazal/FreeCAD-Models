import FreeCAD as App
import FreeCADGui as Gui
import Part
import math
import random

# ================= tweakable =================
density     = 1.0                    # scales how many swords (0.6 = fewer/faster)
steel_color = (0.55, 0.57, 0.62)     # RGB 0-1, None to skip
random.seed(7)                       # fixed seed = reproducible chaos
# =============================================

R = random.uniform
X, Y, Z = App.Vector(1,0,0), App.Vector(0,1,0), App.Vector(0,0,1)
def N(n): return max(1, int(n*density))

# ---------- one (more detailed) sword ----------
def make_sword(L, w=8.0, t=2.6):
    tip = L*0.14
    sil = [(-w/2,0),(w/2,0),(w/2,L-tip),(0,L),(-w/2,L-tip),(-w/2,0)]
    blade = Part.Face(Part.makePolygon([App.Vector(a,0,b) for a,b in sil])).extrude(App.Vector(0,t,0))
    blade.translate(App.Vector(0,-t/2,0))

    sw, sp = w*0.16, t*1.05                                   # central fuller ridge
    dia = [(sw,0),(0,sp),(-sw,0),(0,-sp),(sw,0)]
    spine = Part.Face(Part.makePolygon([App.Vector(a,b,0) for a,b in dia])).extrude(App.Vector(0,0,L-tip))

    guard  = Part.makeBox(w*3.0, t*2.6, w*0.7, App.Vector(-w*1.5, -t*1.3, -w*0.7))
    gl     = w*1.8
    grip   = Part.makeCylinder(w*0.34, gl, App.Vector(0,0,-w*0.7-gl), App.Vector(0,0,1))
    pommel = Part.makeSphere(w*0.5, App.Vector(0,0,-w*0.7-gl))
    return Part.makeCompound([blade, spine, guard, grip, pommel])

# ---------- placement ----------
def place(s, pos, rx=0, ry=0, rz=0):
    s.translate(pos)
    if rx: s.rotate(pos, X, rx)
    if ry: s.rotate(pos, Y, ry)
    if rz: s.rotate(pos, Z, rz)
    return s

parts = []
def add(L, pos, rx=0, ry=0, rz=0, w=8.0):
    parts.append(place(make_sword(L, w), App.Vector(*pos), rx, ry, rz))

# ---- BASE: tangled near-horizontal pile ----
for _ in range(N(30)):
    add(R(90,165), (R(-115,115), R(-105,80), R(8,70)),
        rx=-90+R(-22,22), ry=R(-15,15), rz=R(0,360), w=R(6,8))

# ---- PEDESTAL: bridges base up to the seat ----
for _ in range(N(18)):
    add(R(120,200), (R(-75,75), R(-70,40), R(55,90)),
        rx=R(-20,20), ry=R(-25,25), rz=R(-30,30), w=R(6,8))

# ---- SEAT: forward-laid blades form the sitting surface ----
seatz = 150
for _ in range(N(16)):
    add(R(150,205), (R(-72,72), -62, seatz+R(-6,8)), rx=-90+R(-6,6), rz=R(-22,22), w=R(7,9))
for _ in range(N(5)):
    add(R(110,150), (R(-70,70), R(20,55), seatz+R(-4,6)), rx=-90+R(-8,8), rz=90+R(-30,30), w=7)

# ---- ARMS: bristling clusters on both sides ----
for side in (-1, 1):
    for _ in range(N(10)):
        add(R(120,205), (side*R(78,95), R(-60,15), R(150,180)),
            rx=R(-12,14), ry=side*R(22,58), rz=R(-15,15), w=R(6,8))

# ---- BACK: towering dense fan, several rows ----
for r in range(5):
    cnt = N(15 - r*2)
    ybase, zbase = -52 - r*9, 150 + r*7
    for k in range(cnt):
        frac = 0.0 if cnt == 1 else (k/(cnt-1))*2 - 1
        x = frac*(95 + r*4)
        L = (235 + r*32) * (1 + 0.14*math.cos(frac*math.pi)) * R(0.9,1.08)
        add(L, (x, ybase+R(-5,5), zbase),
            rx=R(6,18), ry=frac*(20+r*3)+R(-7,7), rz=R(-8,8), w=R(7,9))

# ---- SCATTER: chaotic swords to fuse the mass ----
for _ in range(N(16)):
    add(R(110,230), (R(-110,110), R(-90,-30), R(170,330)),
        rx=R(-25,30), ry=R(-45,45), rz=R(-20,20), w=R(6,8))

throne = Part.makeCompound(parts)

# ---------- document ----------
doc_name = "IronThrone"
if doc_name in App.listDocuments():
    doc = App.getDocument(doc_name)
    for o in list(doc.Objects):
        doc.removeObject(o.Name)
else:
    doc = App.newDocument(doc_name)
App.setActiveDocument(doc.Name)

obj = doc.addObject("Part::Feature", "IronThrone")
obj.Shape = throne
doc.recompute()

if steel_color:
    try:
        obj.ViewObject.ShapeColor = steel_color
    except Exception:
        pass

Gui.activeDocument().activeView().viewIsometric()
Gui.SendMsgToActiveView("ViewFit")
